module optical-translator-impl-mock {
    yang-version 1;
    namespace "urn:opendaylight:params:xml:ns:yang:optical-translator:impl:emulated";
    prefix "optical-translator-impl-mock";

    import config { prefix config; revision-date 2013-04-05; }
    import opendaylight-md-sal-binding { prefix md-sal-binding; revision-date 2013-10-28;}

    description
        "Service definition for optical-translator-mock project";

    revision "2016-12-28" {
        description
            "Initial revision";
    }

    identity optical-translator-mock {
        base config:module-type;
        config:java-name-prefix OpticalTranslatorMock;
    }

    augment "/config:modules/config:module/config:configuration" {
        case optical-translator-mock{
            when "/config:modules/config:module/config:type = 'optical-translator-mock'";
            container broker {
                uses config:service-ref {
                    refine type {
                        mandatory true;
                        config:required-identity md-sal-binding:binding-broker-osgi-registry;
                    }
                }
            }
        }
    }
}
