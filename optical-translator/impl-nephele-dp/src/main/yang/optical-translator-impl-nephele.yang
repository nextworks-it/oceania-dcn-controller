module optical-translator-impl-nephele {
    yang-version 1;
    namespace "urn:opendaylight:params:xml:ns:yang:optical-translator:impl:nephele";
    prefix "optical-translator-impl-nephele";

    import config { prefix config; revision-date 2013-04-05; }
    import opendaylight-md-sal-binding { prefix md-sal-binding; revision-date 2013-10-28;}

    description
        "Service definition for optical-translator-nephele project";

    revision "2016-12-28" {
        description
            "Initial revision";
    }

    identity optical-translator-nephele {
        base config:module-type;
        config:java-name-prefix OpticalTranslatorNephele;
    }

    augment "/config:modules/config:module/config:configuration" {
        case optical-translator-nephele{
            when "/config:modules/config:module/config:type = 'optical-translator-nephele'";
            container broker {
                uses config:service-ref {
                    refine type {
                        mandatory true;
                        config:required-identity md-sal-binding:binding-broker-osgi-registry;
                    }
                }
            }
        }
    }
}
